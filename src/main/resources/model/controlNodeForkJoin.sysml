action controlNodeForkJoin{
	first start;
	then action  action1;
	then fork1;
	action action2;
	then join1;
 	fork fork1;
	then action3;
	then action2;
	action action3;
	then join1;
	join join1;
	then action5;
	action action5;
	then done;
}
